# APUCM

## 8116: RS_UCM_00015
UCM shall remove all unneeded data such as logs, possible backups after Software Package processing has finished.
- project: 29
- applies_to: -
- dependencies: -
- globalId: GID-60202
- documentKey: AreneOS-RefAPUCM-7
- rationale: UCM shall make sure all unneeded resources are freed after Software Package processing has finished.
- requirement: UCM shall remove all unneeded data after Software Package processing has finished.
- supporting_material: -
- type: Draft
- up_trace_link: RS_Main_00150, RS_Main_00503
- use_case: At the end of update process UCM shall remove log files, stored backups for Software Package and other temporary items created during update process.
