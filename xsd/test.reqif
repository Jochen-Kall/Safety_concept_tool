# TITLE of the Document to be exported

# Specification: Safety Goal
- name: Safety Goal
- description: Safety Goal

## safety_goal_set: Safety Goal (set)

### ID_971613141
Safety Goal 1
- asil: B
- type: SG
- Derive Relationship -> ID_284275189

### ID_759203603
Safety Goal 2
- asil: A
- type: SG

# Specification: Functional safety Requirements
- name: Functional safety Requirements
- description: Functional safety Requirements

## fsr_set: Functional Safety Requirement (set)

### ID_284275189
AAAA
- asil: B
- type: FSR
- allocation: Sys Element 1
- Derive Relationship -> ID_1880247567

### ID_248064249
HHHHHH
- asil: B
- type: FSR
- allocation: Not Allocated
- Derive Relationship -> ID_759203603

# Specification: Technical safety Requirements
- name: Technical safety Requirements
- description: Technical safety Requirements

## tsr_set: Technical Safety Requirement (set)

### ID_1880247567
BBBBB
- asil: B
- type: TSR
- allocation: Sys Element 1
- Derive Relationship -> ID_1226725815

### ID_1489745809
CCCCC
- asil: B
- type: TSR
- allocation: Sys Element 2
- Derive Relationship -> ID_1516169837

# Specification: Hardware safety Requirements
- name: Hardware safety Requirements
- description: Hardware safety Requirements

## hsr_set: Hardware Safety Requirement (set)

### ID_1226725815
DDDDD
- asil: B
- type: HW
- allocation: HW Element 1
- Derive Relationship -> ID_166025809

### ID_1516169837
FFFFF
- asil: B
- type: HW
- allocation: HW Element 2
- Derive Relationship -> ID_685136060

# Specification: Software safety Requirements
- name: Software safety Requirements
- description: Software safety Requirements

## ssr_set: Software Safety Requirement (set)

### ID_166025809
EEEEE
- asil: B
- type: SW
- allocation: SW Element 2
- Derive Relationship -> ID_1489745809

### ID_685136060
GGGGG
- asil: B
- type: SW
- allocation: SW Element 2
- Derive Relationship -> ID_248064249
